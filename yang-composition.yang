module yang-composition {
  prefix yc;

  organization
    "Corenova R&D Group";

  contact
    "Web:  <http://www.corenova.com>
     Code: <http://github.com/corenova/yang-cc>

     Author: Peter K. Lee <mailto:peter@corenova.com>";

  description
    "This module provides YANG multi-schema composition";

  revision 2016-04-06 {
    description "Initial Version";
  }
  
  extension composition {
    description
      "Defines a block of one or more specification(s) and module(s) being combined into a singular bundle.";
  }

  extension link-action {
    argument target-action-node;
    description
      "Defines a source link that implements a given module's action operation (rpc, notification)";
  }
}
